MTXC-M3UA-MIB DEFINITIONS ::= BEGIN

IMPORTS
		MODULE-IDENTITY, OBJECT-TYPE,
		Unsigned32, Counter32, Counter64, mib-2
			FROM SNMPv2-SMI
		InetAddressType, InetAddress
			FROM INET-ADDRESS-MIB
		mtxcExperiment
			FROM MTXC-SMI
		TruthValue, DisplayString
			FROM SNMPv2-TC
		MODULE-COMPLIANCE, OBJECT-GROUP
			FROM SNMPv2-CONF;

--

m3uaMIB MODULE-IDENTITY
		LAST-UPDATED "201806250000Z"
		ORGANIZATION "MTX Connect"
		CONTACT-INFO
			"MTX Connect S.a r.l."
		DESCRIPTION
			"The MIB module for entities implementing the
			 SIGTRAN MTP3-User Adaptation Layer (M3UA) (RFC4666).
			
			 Copyright (C) The Internet Society (2003).
			
			 The initial version of this MIB module was published
			 as IETF draft draft-ietf-sigtran-m3ua-mib-07, and this
			 module descends from SigScale's rendering of it under
			 the Apache 2.0 licence of their m3ua application. What
			 changed here is where it hangs: our own enterprise arc
			 rather than theirs, so that no host needs the
			 sigscale_mibs application to compile it.

			 It may be deprecated when an RFC is published"
	::= {mtxcExperiment 1}

-- Top-level structure of the MIB

m3uaManagement  OBJECT IDENTIFIER ::= { m3uaMIB 1 }
m3uaConformance OBJECT IDENTIFIER ::= { m3uaMIB 2 }
m3uaAttributes  OBJECT IDENTIFIER ::= { m3uaManagement 1 }
m3uaConfig      OBJECT IDENTIFIER ::= { m3uaAttributes 1 }
m3uaStatistics  OBJECT IDENTIFIER ::= { m3uaAttributes 2 }
m3uaTables      OBJECT IDENTIFIER ::= { m3uaManagement 2 }
m3uaEp          OBJECT IDENTIFIER ::= { m3uaTables 1 }
m3uaEpCfg       OBJECT IDENTIFIER ::= { m3uaEp 1 }
m3uaEpStat      OBJECT IDENTIFIER ::= { m3uaEp 2 }
m3uaAsp         OBJECT IDENTIFIER ::= { m3uaTables 2 }
m3uaAspCfg      OBJECT IDENTIFIER ::= { m3uaAsp 1 }
m3uaAspStat     OBJECT IDENTIFIER ::= { m3uaAsp 2 }
m3uaSgpIpsp     OBJECT IDENTIFIER ::= { m3uaTables 3 }
m3uaSgpIpspCfg  OBJECT IDENTIFIER ::= { m3uaSgpIpsp 1 }
m3uaSgpIpspStat OBJECT IDENTIFIER ::= { m3uaSgpIpsp 2 }
m3uaGen         OBJECT IDENTIFIER ::= { m3uaTables 4 }
m3uaGenCfg      OBJECT IDENTIFIER ::= { m3uaGen 1 }
m3uaGenStat     OBJECT IDENTIFIER ::= { m3uaGen 2 }


m3uaRoutingFailures OBJECT-TYPE
		SYNTAX      Counter64
		MAX-ACCESS  read-only
		STATUS      current
		DESCRIPTION
			"The number of times a routing operation against Routing
			 Table fails. No final SCTP Association ID is obtained from
			 the routing operation. That is the reason why this is a
			 general statistic instead a per association statistic."
	::= { m3uaStatistics 1 }

m3uaEndPointTable OBJECT-TYPE
		SYNTAX      SEQUENCE OF M3uaEndPointEntry
		MAX-ACCESS  not-accessible
		STATUS      current
		DESCRIPTION
			"A table describing SCTP endpoints."
	::= { m3uaEpCfg 1 }

m3uaEndPointEntry OBJECT-TYPE
		SYNTAX      M3uaEndPointEntry
		MAX-ACCESS  not-accessible
		STATUS      current
		DESCRIPTION
			"SCTP endpoint configuration."
		INDEX   { m3uaEpIndex }
	::= { m3uaEndPointTable 1 }

M3uaEndPointEntry ::= SEQUENCE {
		m3uaEpIndex           Unsigned32,
		m3uaEpType            INTEGER,
		m3uaLocalAddressType  InetAddressType,
		m3uaLocalAddress      InetAddress,
		m3uaLocalPort         INTEGER,
		m3uaRemoteAddressType InetAddressType,
		m3uaRemoteAddress     InetAddress,
		m3uaRemotePort        INTEGER,
		m3uaProcType          INTEGER,
		m3uaVersion           Unsigned32,
		m3uaTrInitValue       Unsigned32,
		m3uaTPAudInitValue    Unsigned32,
		m3uaHeartBeat         TruthValue,
		m3uaTBeatInitValue    Unsigned32,
		m3uaTAckInitValue     Unsigned32
	}

m3uaEpIndex OBJECT-TYPE
		SYNTAX       Unsigned32 (1..4294967295)
		MAX-ACCESS   not-accessible
		STATUS       current
		DESCRIPTION
			"A number uniquely identifying each SCTP endpoint."
	::= { m3uaEndPointEntry 1 }

m3uaEpType OBJECT-TYPE
		SYNTAX       INTEGER {
			client(1),
			server(2)
		}
		MAX-ACCESS   read-only
		STATUS       current
		DESCRIPTION
			"The endpoint type is either accepting incoming connections
			 (server) or establishing outgoing connections (client)."
	::= { m3uaEndPointEntry 2 }

m3uaLocalAddressType OBJECT-TYPE
		SYNTAX       InetAddressType
		MAX-ACCESS   read-only
		STATUS       current
		DESCRIPTION
			"The primary local IP address type of the endpoint."
	::= { m3uaEndPointEntry 3 }

m3uaLocalAddress  OBJECT-TYPE
		SYNTAX       InetAddress
		MAX-ACCESS   read-only
		STATUS       current
		DESCRIPTION
			"The primary local IP address of the endpoint."
	::= { m3uaEndPointEntry 4 }

m3uaLocalPort OBJECT-TYPE
		SYNTAX       INTEGER (0..65535)
		MAX-ACCESS   read-only
		STATUS       current
		DESCRIPTION
			"The primary local IP port of the endpoint."
	::= { m3uaEndPointEntry 5 }

m3uaRemoteAddressType OBJECT-TYPE
		SYNTAX       InetAddressType
		MAX-ACCESS   read-only
		STATUS       current
		DESCRIPTION
			"The primary remote IP address type of the endpoint."
	::= { m3uaEndPointEntry 6 }

m3uaRemoteAddress  OBJECT-TYPE
		SYNTAX       InetAddress
		MAX-ACCESS   read-only
		STATUS       current
		DESCRIPTION
			"The primary remote IP address of the endpoint."
	::= { m3uaEndPointEntry 7 }

m3uaRemotePort OBJECT-TYPE
		SYNTAX       INTEGER (0..65535)
		MAX-ACCESS   read-only
		STATUS       current
		DESCRIPTION
			"The primary remote IP port of the endpoint."
	::= { m3uaEndPointEntry 8 }

m3uaProcType OBJECT-TYPE
		SYNTAX      INTEGER {
			sgp(1),     -- Signaling Gateway Process
			asp(2),     -- Application Server Process
			ipsp(3)     -- IP Server Process
		}
		MAX-ACCESS  read-only
		STATUS      current
		DESCRIPTION
			"This variable indicates the type of the process where the
			 M3UA layer is located."
	::= { m3uaEndPointEntry 9 }

m3uaVersion OBJECT-TYPE
		SYNTAX      Unsigned32
		MAX-ACCESS  read-only
		STATUS      current
		DESCRIPTION
			"Identifies the current version of the M3UA."
	::= { m3uaEndPointEntry 10 }

m3uaTrInitValue OBJECT-TYPE
		SYNTAX      Unsigned32
		UNITS       "milliseconds"
		MAX-ACCESS  read-only
		STATUS      current
		DESCRIPTION
			"Initial value of the Failover timer Tr. Tr set with value 0
			 disables buffering."
		DEFVAL {3000}  -- 3000 milliseconds is the recommended value
	::= { m3uaEndPointEntry 11 }

m3uaTPAudInitValue OBJECT-TYPE
		SYNTAX      Unsigned32
		UNITS       "milliseconds"
		MAX-ACCESS  read-only
		STATUS      current
		DESCRIPTION
			"Initial value of the Periodic Audit timer TPAud."
		DEFVAL {5000}  -- 5000 milliseconds is the recommended value
	::= { m3uaEndPointEntry 12 }

m3uaHeartBeat OBJECT-TYPE
		SYNTAX      TruthValue
		MAX-ACCESS  read-only
		STATUS      current
		DESCRIPTION
			"Activates or deactivates the heartbeat procedure at M3UA
			 level.

			 When the object is set to 'true' (1), the heartbeat procedure
			 is enabled.

			 When the object is set to 'false' (2), Heartbeat is disabled.
			 No BEAT messages are sent but the BEAT messages received are
			 responded."
	::= { m3uaEndPointEntry 13 }

m3uaTBeatInitValue OBJECT-TYPE
		SYNTAX      Unsigned32
		UNITS       "milliseconds"
		MAX-ACCESS  read-only
		STATUS      current
		DESCRIPTION
			"Initial value of the HeartBeat timer TBeat."
		DEFVAL {1000}  -- 1000 milliseconds is the recommended value
	::= { m3uaEndPointEntry 14 }

m3uaTAckInitValue OBJECT-TYPE
		SYNTAX      Unsigned32
		UNITS       "milliseconds"
		MAX-ACCESS  read-only
		STATUS      current
		DESCRIPTION
			"Initial value of the Retransmission timer TAck."
		DEFVAL {2000}  -- 2000 milliseconds is the recommended value
	::= { m3uaEndPointEntry 15 }

m3uaAspDestTable OBJECT-TYPE
		SYNTAX      SEQUENCE OF M3uaAspDestEntry
		MAX-ACCESS  not-accessible
		STATUS      current
		DESCRIPTION
			"A table containing per SS7 destination information. The
			 state of destinations through each SG can be fetched per AS."
	::= { m3uaAspCfg 1 }

m3uaAspDestEntry OBJECT-TYPE
		SYNTAX      M3uaAspDestEntry
		MAX-ACCESS  not-accessible
		STATUS      current
		DESCRIPTION
			"Destination parameters and relation with SGs and ASes."
		INDEX   { m3uaAspDestNa, m3uaAspDestDpc,
			m3uaAspDestSgId, m3uaAspDestAsId }
	::= { m3uaAspDestTable 1 }

M3uaAspDestEntry ::= SEQUENCE {
		m3uaAspDestNa                 Unsigned32,
		m3uaAspDestDpc                Unsigned32,
		m3uaAspDestSgId               Unsigned32,
		m3uaAspDestAsId               Unsigned32,
		m3uaAspDestState              INTEGER
	}

m3uaAspDestNa OBJECT-TYPE
		SYNTAX      Unsigned32
		MAX-ACCESS  not-accessible
		STATUS      current
		DESCRIPTION
			"Network Appearance. When this parameter is not used, Network
			 Indicator parameter, as included in the MTP3 message, will be
			 filled in."
	::= { m3uaAspDestEntry 1 }

m3uaAspDestDpc OBJECT-TYPE
		SYNTAX      Unsigned32
		MAX-ACCESS  not-accessible
		STATUS      current
		DESCRIPTION
			"Destination Point Code located in the SS7 network. It is the
			 final destination for the message generated in the ASP which
			 should reach the SS7 node traversing a Signaling Gateway."
	::= { m3uaAspDestEntry 2 }

m3uaAspDestSgId OBJECT-TYPE
		SYNTAX      Unsigned32
		MAX-ACCESS  not-accessible
		STATUS      current
		DESCRIPTION
			"Signaling Gateway (SG) Identifier. It represents an SG that
			 is in the way to the final DPC located in the SS7 network."
	::= { m3uaAspDestEntry 3 }

m3uaAspDestAsId OBJECT-TYPE
		SYNTAX      Unsigned32
		MAX-ACCESS  not-accessible
		STATUS      current
		DESCRIPTION
			"Application Server (AS) Identifier. It represents an AS that
			 is being served by the ASP. A specific destination address
			 could be reachable or not from the ASP, depending on each AS
			 this ASP is serving to."
	::= { m3uaAspDestEntry 4 }

m3uaAspDestState OBJECT-TYPE
		SYNTAX      INTEGER {
			unknown (1),
			available(2),
			unavailable(3),
			congested(4),
			restricted(5)
		}
		MAX-ACCESS  read-only
		STATUS      current
		DESCRIPTION
			"Destination reachability status. It is the status of the
			 Signaling Point that is the final destination of a message
			 within the SS7 network when the message travels through the
			 Signaling Gateway (SG) identified by the m3uaAspDestSgId
			 object."
	::= { m3uaAspDestEntry 5 }

m3uaAspSgpTable OBJECT-TYPE
		SYNTAX      SEQUENCE OF M3uaAspSgpEntry
		MAX-ACCESS  not-accessible
		STATUS      current
		DESCRIPTION
			"A table containing SGP status information for each SG that
			 is communicating with an AS served by this ASP."
	::= { m3uaAspCfg 2 }

m3uaAspSgpEntry OBJECT-TYPE
		SYNTAX      M3uaAspSgpEntry
		MAX-ACCESS  not-accessible
		STATUS      current
		DESCRIPTION
			"SGP related parameters. There are SGPs available depending
			 on the AS the ASP is serving and the SG it wants to send the
			 messages. It may be one or more SGP for each AS-SG pair."
		INDEX   { m3uaAspSgpAsId, m3uaAspSgpId }
	::= { m3uaAspSgpTable 1 }

M3uaAspSgpEntry ::= SEQUENCE {
		m3uaAspSgpAsId                Unsigned32,
		m3uaAspSgpId                  Unsigned32,
		m3uaAspSgpState               INTEGER,
		m3uaAspSgpAsName              DisplayString
	}

m3uaAspSgpAsId OBJECT-TYPE
		SYNTAX      Unsigned32
		MAX-ACCESS  not-accessible
		STATUS      current
		DESCRIPTION
			"Application Server (AS) Identifier. It represents an AS that
			 is being served by the ASP."
	::= { m3uaAspSgpEntry 1 }

m3uaAspSgpId OBJECT-TYPE
		SYNTAX      Unsigned32
		MAX-ACCESS  not-accessible
		STATUS      current
		DESCRIPTION
			"Signaling Gateway Process (SGP) Identifier. It represents an
			 SGP that is serving the Signaling Gateway (SG) identified by
			 the m3uaAspSgpSgId object."
	::= { m3uaAspSgpEntry 2 }

m3uaAspSgpState OBJECT-TYPE
		SYNTAX      INTEGER {
			unknown (1),
			active(2),
			inactive(3),
			down(4)
		}
		MAX-ACCESS  read-only
		STATUS      current
		DESCRIPTION
			"AS state through each SGP in the SG."
	::= { m3uaAspSgpEntry 3 }

m3uaAspSgpAsName OBJECT-TYPE
		SYNTAX      DisplayString
		MAX-ACCESS  read-only
		STATUS      current
		DESCRIPTION
			"Application Server local name."
	::= { m3uaAspSgpEntry 4 }

m3uaAspAssocTable OBJECT-TYPE
		SYNTAX      SEQUENCE OF M3uaAspAssocEntry
		MAX-ACCESS  not-accessible
		STATUS      current
		DESCRIPTION
			"A table containing SCTP association information information
			 for each SGP that is communicating with this ASP."
	::= { m3uaAspCfg 3 }

m3uaAspAssocEntry OBJECT-TYPE
		SYNTAX      M3uaAspAssocEntry
		MAX-ACCESS  not-accessible
		STATUS      current
		DESCRIPTION
			"SCTP related parameters. There will be one association to
			 each of the SGPs that this ASP has to talk to."
		INDEX   { m3uaAspAssocSgpId }
	::= { m3uaAspAssocTable 1 }

M3uaAspAssocEntry ::= SEQUENCE {
		m3uaAspAssocSgpId             Unsigned32,
		m3uaAspAssocId                Unsigned32,
		m3uaAspAssocMinOutStreams     Unsigned32,
		m3uaAspAssocMaxInStreams      Unsigned32
	}

m3uaAspAssocSgpId OBJECT-TYPE
		SYNTAX      Unsigned32
		MAX-ACCESS  not-accessible
		STATUS      current
		DESCRIPTION
			"Signaling Gateway Process (SGP) Identifier. It represents an SGP."
	::= { m3uaAspAssocEntry 1 }

m3uaAspAssocId OBJECT-TYPE
		SYNTAX      Unsigned32
		MAX-ACCESS  read-only
		STATUS      current
		DESCRIPTION
			"Association Identification. It is the value that identifies
			 the association that is established between this ASP and the
			 SGP represented by m3uaAspAssocSgpId. This value is extracted
			 from the SCTP association Id value returned by SCTP when the
			 association is established to that endpoint. It is the link
			 to get the transport values from the SCTP MIB."
	::= { m3uaAspAssocEntry 2 }

m3uaAspAssocMinOutStreams OBJECT-TYPE
		SYNTAX      Unsigned32
		MAX-ACCESS  read-only
		STATUS      current
		DESCRIPTION
			"If the SCTP association is initiated from this ASP,
			 this will be the minimum number of outgoing streams that is
			 requested to the remote peer at association start up."
	::= { m3uaAspAssocEntry 3 }

m3uaAspAssocMaxInStreams OBJECT-TYPE
		SYNTAX      Unsigned32
		MAX-ACCESS  read-only
		STATUS      current
		DESCRIPTION
			"It is the maximum number of input streams that this
			 application can support. It is used during the Association
			 establishment phase."
	::= { m3uaAspAssocEntry 4 }

m3uaAspRcTable OBJECT-TYPE
		SYNTAX      SEQUENCE OF M3uaAspRcEntry
		MAX-ACCESS  not-accessible
		STATUS      current
		DESCRIPTION
			"A table containing the Routing Context (RC) values for each
			 SGP-AS relationship. As indicated in the M3UA RFC, the RC
			 values are SGP scoped."
	::= { m3uaAspCfg 4 }

m3uaAspRcEntry OBJECT-TYPE
		SYNTAX      M3uaAspRcEntry
		MAX-ACCESS  not-accessible
		STATUS      current
		DESCRIPTION
			" RC value for each AS as assigned by the SGP."
		INDEX   { m3uaAspRcSgpId, m3uaAspRcAsId }
	::= { m3uaAspRcTable 1 }

M3uaAspRcEntry ::= SEQUENCE {
		m3uaAspRcSgpId                Unsigned32,
		m3uaAspRcAsId                 Unsigned32,
		m3uaAspRcValue                Unsigned32
	}

m3uaAspRcSgpId OBJECT-TYPE
		SYNTAX      Unsigned32
		MAX-ACCESS  not-accessible
		STATUS      current
		DESCRIPTION
			"Signaling Gateway Process (SGP) Identifier. It represents an
			 SGP that communicates with this ASP."
	::= { m3uaAspRcEntry 1 }

m3uaAspRcAsId OBJECT-TYPE
		SYNTAX      Unsigned32
		MAX-ACCESS  not-accessible
		STATUS      current
		DESCRIPTION
			"Application Server (AS) Identifier. It represents an AS that
			 is being served by the ASP."
	::= { m3uaAspRcEntry 2 }

m3uaAspRcValue OBJECT-TYPE
		SYNTAX      Unsigned32
		MAX-ACCESS  read-only
		STATUS      current
		DESCRIPTION
			"This is the value for the Routing Context that is share
			 between the SGP identified by communicatinm3uaAspRcSgpId
			 object and this ASP when serving to AS identified by the
			 m3uaAspRcAsId object."
	::= { m3uaAspRcEntry 3 }

m3uaAspStatTable OBJECT-TYPE
		SYNTAX      SEQUENCE OF M3uaAspStatEntry
		MAX-ACCESS  not-accessible
		STATUS      current
		DESCRIPTION
			"A table containing per association statistics."
	::= { m3uaAspStat 1 }

m3uaAspStatEntry OBJECT-TYPE
		SYNTAX      M3uaAspStatEntry
		MAX-ACCESS  not-accessible
		STATUS      current
		DESCRIPTION
			"It counts all the messages received and sent through a
			 specific association."
		INDEX   { m3uaAspStatAssocId }
	::= { m3uaAspStatTable 1 }

M3uaAspStatEntry ::= SEQUENCE {
		m3uaAspStatAssocId            Unsigned32,
		m3uaAspStatAspupOut           Counter32,
		m3uaAspStatAspacOut           Counter32,
		m3uaAspStatAspdnOut           Counter32,
		m3uaAspStatAspiaOut           Counter32,
		m3uaAspStatAspupAckIn         Counter32,
		m3uaAspStatAspacAckIn         Counter32,
		m3uaAspStatAspdnAckIn         Counter32,
		m3uaAspStatAspiaAckIn         Counter32,
		m3uaAspStatNotifyIn           Counter32,
		m3uaAspStatDaudOut            Counter32,
		m3uaAspStatDunaIn             Counter32,
		m3uaAspStatDavaIn             Counter32,
		m3uaAspStatDupuIn             Counter32
	}

m3uaAspStatAssocId OBJECT-TYPE
		SYNTAX      Unsigned32
		MAX-ACCESS  not-accessible
		STATUS      current
		DESCRIPTION
			"Association Identification. It is the value that identifies
			 the association that is established between this ASP and the
			 SGP represented by m3uaAspAssocSgpId. This value is extracted
			 from the SCTP association Id value returned by SCTP when the
			 association is established to that endpoint. It is the link
			 to get the transport values from the SCTP MIB."
	::= { m3uaAspStatEntry 1 }

m3uaAspStatAspupOut OBJECT-TYPE
		SYNTAX      Counter32
		MAX-ACCESS  read-only
		STATUS      current
		DESCRIPTION
			"Number of ASPUP messages sent through the association."
	::= { m3uaAspStatEntry 2 }

m3uaAspStatAspacOut OBJECT-TYPE
		SYNTAX      Counter32
		MAX-ACCESS  read-only
		STATUS      current
		DESCRIPTION
			"Number of ASPAC messages sent through the association."
	::= { m3uaAspStatEntry 3 }

m3uaAspStatAspdnOut OBJECT-TYPE
		SYNTAX      Counter32
		MAX-ACCESS  read-only
		STATUS      current
		DESCRIPTION
			"Number of ASPDN messages sent through the association."
	::= { m3uaAspStatEntry 4 }

m3uaAspStatAspiaOut OBJECT-TYPE
		SYNTAX      Counter32
		MAX-ACCESS  read-only
		STATUS      current
		DESCRIPTION
			"Number of ASPIA messages sent through the association."
	::= { m3uaAspStatEntry 5 }

m3uaAspStatAspupAckIn OBJECT-TYPE
		SYNTAX      Counter32
		MAX-ACCESS  read-only
		STATUS      current
		DESCRIPTION
			"Number of ASPUP ACK messages received through the
			 association."
	::= { m3uaAspStatEntry 6 }

m3uaAspStatAspacAckIn OBJECT-TYPE
		SYNTAX      Counter32
		MAX-ACCESS  read-only
		STATUS      current
		DESCRIPTION
			"Number of ASPAC ACK messages received through the
			 association."
	::= { m3uaAspStatEntry 7 }

m3uaAspStatAspdnAckIn OBJECT-TYPE
		SYNTAX      Counter32
		MAX-ACCESS  read-only
		STATUS      current
		DESCRIPTION
			"Number of ASPDN ACK messages received through the
			 association."
	::= { m3uaAspStatEntry 8 }

m3uaAspStatAspiaAckIn OBJECT-TYPE
		SYNTAX      Counter32
		MAX-ACCESS  read-only
		STATUS      current
		DESCRIPTION
			"Number of ASPIA ACK messages received through the
			 association."
	::= { m3uaAspStatEntry 9 }

m3uaAspStatNotifyIn OBJECT-TYPE
		SYNTAX      Counter32
		MAX-ACCESS  read-only
		STATUS      current
		DESCRIPTION
			"Number of NOTIFY messages received through the
			 association."
	::= { m3uaAspStatEntry 10 }

m3uaAspStatDaudOut OBJECT-TYPE
		SYNTAX      Counter32
		MAX-ACCESS  read-only
		STATUS      current
		DESCRIPTION
			"Number of DAUD messages sent through the association."
	::= { m3uaAspStatEntry 11 }

m3uaAspStatDunaIn OBJECT-TYPE
		SYNTAX      Counter32
		MAX-ACCESS  read-only
		STATUS      current
		DESCRIPTION
			"Number of DUNA messages received through the association."
	::= { m3uaAspStatEntry 12 }

m3uaAspStatDavaIn OBJECT-TYPE
		SYNTAX      Counter32
		MAX-ACCESS  read-only
		STATUS      current
		DESCRIPTION
			"Number of DAVA messages received through the association."
	::= { m3uaAspStatEntry 13 }

m3uaAspStatDupuIn OBJECT-TYPE
		SYNTAX      Counter32
		MAX-ACCESS  read-only
		STATUS      current
		DESCRIPTION
			"Number of DUPU messages received through the association."
	::= { m3uaAspStatEntry 14 }

m3uaSgpIpspRtgTable OBJECT-TYPE
		SYNTAX      SEQUENCE OF M3uaSgpIpspRtgEntry
		MAX-ACCESS  not-accessible
		STATUS      current
		DESCRIPTION
			"A table containing Routing-specific information."
	::= { m3uaSgpIpspCfg 1 }

m3uaSgpIpspRtgEntry OBJECT-TYPE
		SYNTAX      M3uaSgpIpspRtgEntry
		MAX-ACCESS  not-accessible
		STATUS      current
		DESCRIPTION
			"General common variables for a Routing Key."
		INDEX   {
			m3uaSgpIpspRtgNa,
			m3uaSgpIpspRtgDpc,
			m3uaSgpIpspRtgSi,
			m3uaSgpIpspRtgOpc }
	::= { m3uaSgpIpspRtgTable 1 }

M3uaSgpIpspRtgEntry ::= SEQUENCE {
		m3uaSgpIpspRtgNa             Unsigned32,
		m3uaSgpIpspRtgDpc            Unsigned32,
		m3uaSgpIpspRtgSi             Unsigned32,
		m3uaSgpIpspRtgOpc            Unsigned32,
		m3uaSgpIpspRtgAsId           Unsigned32,
		m3uaSgpIpspRtgRc             Unsigned32
	}

m3uaSgpIpspRtgNa OBJECT-TYPE
		SYNTAX      Unsigned32
		MAX-ACCESS  not-accessible
		STATUS      current
		DESCRIPTION
			"Network Appearance for that routing key. A default value
			 will be assigned if not present in the Routing Key."
	::= { m3uaSgpIpspRtgEntry 1 }

m3uaSgpIpspRtgDpc OBJECT-TYPE
		SYNTAX      Unsigned32
		MAX-ACCESS  not-accessible
		STATUS      current
		DESCRIPTION
			"Destination Point Code for that routing key. A default
			 value will be assigned if not present in the Routing Key.
			 Range: 0 - 16777215."
	::= { m3uaSgpIpspRtgEntry 2 }

m3uaSgpIpspRtgSi OBJECT-TYPE
		SYNTAX      Unsigned32
		MAX-ACCESS  not-accessible
		STATUS      current
		DESCRIPTION
			"Service Indicator for that routing key. A default value
			 will be assigned if not present in the Routing Key.
			 Range: 2 - 10."
	::= { m3uaSgpIpspRtgEntry 3 }

m3uaSgpIpspRtgOpc OBJECT-TYPE
		SYNTAX      Unsigned32
		MAX-ACCESS  not-accessible
		STATUS      current
		DESCRIPTION
			"Originating Point Code for that routing key. A default
			 value will be assigned if not present in the Routing Key.
			 Range: 0 to 16777215."
	::= { m3uaSgpIpspRtgEntry 4 }

m3uaSgpIpspRtgAsId OBJECT-TYPE
		SYNTAX      Unsigned32
		MAX-ACCESS  read-only
		STATUS      current
		DESCRIPTION
			"Application Server Identification Value."
	::= { m3uaSgpIpspRtgEntry 5 }

m3uaSgpIpspRtgRc OBJECT-TYPE
		SYNTAX      Unsigned32
		MAX-ACCESS  read-only
		STATUS      current
		DESCRIPTION
			"Routing Context for that routing key."
	::= { m3uaSgpIpspRtgEntry 6 }

m3uaSgpIpspAsTable OBJECT-TYPE
		SYNTAX      SEQUENCE OF M3uaSgpIpspAsEntry
		MAX-ACCESS  not-accessible
		STATUS      current
		DESCRIPTION
			"A table containing Application Server-specific information."
	::= { m3uaSgpIpspCfg 2 }

m3uaSgpIpspAsEntry OBJECT-TYPE
		SYNTAX      M3uaSgpIpspAsEntry
		MAX-ACCESS  not-accessible
		STATUS      current
		DESCRIPTION
			"General common variables for the Application Server"
		INDEX   { m3uaSgpIpspAsId }
	::= { m3uaSgpIpspAsTable 1 }

M3uaSgpIpspAsEntry ::= SEQUENCE {
		m3uaSgpIpspAsId                     Unsigned32,
		m3uaSgpIpspAsState                  INTEGER,
		m3uaSgpIpspAsTmt                    INTEGER,
		m3uaSgpIpspAsName                   DisplayString
	}

m3uaSgpIpspAsId OBJECT-TYPE
		SYNTAX      Unsigned32
		MAX-ACCESS  not-accessible
		STATUS      current
		DESCRIPTION
			"Application Server Identification Value."
	::= { m3uaSgpIpspAsEntry 1 }

m3uaSgpIpspAsState OBJECT-TYPE
		SYNTAX      INTEGER {
			active(1),
			inactive(2),
			down(3),
			pending(4)
		}
		MAX-ACCESS  read-only
		STATUS      current
		DESCRIPTION
			"Current Application Server State. Based on the state
			 of the Application Server Processes which serve it."
	::= { m3uaSgpIpspAsEntry 2 }

m3uaSgpIpspAsTmt OBJECT-TYPE
		SYNTAX      INTEGER {
			override(1),
			loadshare(2),
			broadcast(3)
		}
		MAX-ACCESS  read-only
		STATUS      current
		DESCRIPTION
			"Current Application Server Traffic Mode Type."
	::= { m3uaSgpIpspAsEntry 3 }

m3uaSgpIpspAsName OBJECT-TYPE
		SYNTAX      DisplayString
		MAX-ACCESS  read-only
		STATUS      current
		DESCRIPTION
			"Application Server local name."
	::= { m3uaSgpIpspAsEntry 4 }

m3uaSgpIpspAspTable OBJECT-TYPE
		SYNTAX      SEQUENCE OF M3uaSgpIpspAspEntry
		MAX-ACCESS  not-accessible
		STATUS      current
		DESCRIPTION
			"A table containing Application Server Process-specific
			 information."
	::= { m3uaSgpIpspCfg 3 }

m3uaSgpIpspAspEntry OBJECT-TYPE
		SYNTAX      M3uaSgpIpspAspEntry
		MAX-ACCESS  not-accessible
		STATUS      current
		DESCRIPTION
			"General common variables for the Application Server Process."
		INDEX   { m3uaSgpIpspAspAsId, m3uaSgpIpspAspId }
	::= { m3uaSgpIpspAspTable 1 }

M3uaSgpIpspAspEntry ::= SEQUENCE {
		m3uaSgpIpspAspAsId                        Unsigned32,
		m3uaSgpIpspAspId                          Unsigned32,
		m3uaSgpIpspAspState                       INTEGER,
		m3uaSgpIpspAspRole                        INTEGER
	}

m3uaSgpIpspAspAsId OBJECT-TYPE
		SYNTAX      Unsigned32
		MAX-ACCESS  not-accessible
		STATUS      current
		DESCRIPTION
			"Application Server Identification Value."
	::= { m3uaSgpIpspAspEntry 1 }

m3uaSgpIpspAspId OBJECT-TYPE
		SYNTAX      Unsigned32
		MAX-ACCESS  not-accessible
		STATUS      current
		DESCRIPTION
			" Application Server Process Identification Value."
	::= { m3uaSgpIpspAspEntry 2 }

m3uaSgpIpspAspState OBJECT-TYPE
		SYNTAX      INTEGER {
			aspDown(1),
			aspUp(2),
			aspActive(3)
		}
		MAX-ACCESS  read-only
		STATUS      current
		DESCRIPTION
			"The state of this Application Server Process for a
			 given AS."
	::= { m3uaSgpIpspAspEntry 3 }

m3uaSgpIpspAspRole OBJECT-TYPE
		SYNTAX      INTEGER {
			primary(1),
			backup(2),
			loadsharing(3),
			broadcast (4)
		}
		MAX-ACCESS  read-only
		STATUS      current
		DESCRIPTION
			"The role of this Application Server Process within the
			 traffic mode for each AS."
	::= { m3uaSgpIpspAspEntry 4 }

m3uaSgpIpspAssocTable OBJECT-TYPE
		SYNTAX      SEQUENCE OF M3uaSgpIpspAssocEntry
		MAX-ACCESS  not-accessible
		STATUS      current
		DESCRIPTION
			"A table containing ASP/IPSP Association-specific information."
	::= { m3uaSgpIpspCfg 4 }

m3uaSgpIpspAssocEntry OBJECT-TYPE
		SYNTAX      M3uaSgpIpspAssocEntry
		MAX-ACCESS  not-accessible
		STATUS      current
		DESCRIPTION
			"General common variables for the Association for an ASP."
		INDEX   { m3uaSgpIpspAssocAspId }
	::= { m3uaSgpIpspAssocTable 1 }

M3uaSgpIpspAssocEntry ::= SEQUENCE {
		m3uaSgpIpspAssocAspId                  Unsigned32,
		m3uaSgpIpspAssocId                     Unsigned32,
		m3uaSgpIpspAssocMinOutStreams          Unsigned32,
		m3uaSgpIpspAssocMaxInStreams           Unsigned32
	}

m3uaSgpIpspAssocAspId OBJECT-TYPE
		SYNTAX      Unsigned32
		MAX-ACCESS  not-accessible
		STATUS      current
		DESCRIPTION
			" Application Server Process Identification Value."
	::= { m3uaSgpIpspAssocEntry 1 }

m3uaSgpIpspAssocId  OBJECT-TYPE
		SYNTAX      Unsigned32
		MAX-ACCESS  read-only
		STATUS      current
		DESCRIPTION
			"Association Identification. Value identifying the
			 association for that ASP. This value is extracted from
			 the SCTP association Id value returned by SCTP when the
			 association is established to that endpoint."
	::= { m3uaSgpIpspAssocEntry 2 }

m3uaSgpIpspAssocMinOutStreams OBJECT-TYPE
		SYNTAX      Unsigned32
		MAX-ACCESS  read-only
		STATUS      current
		DESCRIPTION
			"If the SCTP association is initiated from this ASP,
			 this will be the minimum number of outgoing streams that is
			 requested to the remote peer at association start up."
	::= { m3uaSgpIpspAssocEntry 3 }

m3uaSgpIpspAssocMaxInStreams OBJECT-TYPE
		SYNTAX      Unsigned32
		MAX-ACCESS  read-only
		STATUS      current
		DESCRIPTION
			"It is the maximum number of input streams that this
			 application can support. It is used during the Association
			 establishment phase."
	::= { m3uaSgpIpspAssocEntry 4 }

m3uaSgpIpspStatTable OBJECT-TYPE
		SYNTAX      SEQUENCE OF M3uaSgpIpspStatEntry
		MAX-ACCESS  not-accessible
		STATUS      current
		DESCRIPTION
			"A table containing per association statistics."
	::= { m3uaSgpIpspStat 1 }

m3uaSgpIpspStatEntry OBJECT-TYPE
		SYNTAX      M3uaSgpIpspStatEntry
		MAX-ACCESS  not-accessible
		STATUS      current
		DESCRIPTION
			"It counts all the messages received and sent through a
			 specific association."
		INDEX   { m3uaSgpIpspStatAssocId }
	::= { m3uaSgpIpspStatTable 1 }

M3uaSgpIpspStatEntry ::= SEQUENCE {
		m3uaSgpIpspStatAssocId            Unsigned32,
		m3uaSgpIpspStatAspupAckOut        Counter32,
		m3uaSgpIpspStatAspacAckOut        Counter32,
		m3uaSgpIpspStatAspdnAckOut        Counter32,
		m3uaSgpIpspStatAspiaAckOut        Counter32,
		m3uaSgpIpspStatAspupIn            Counter32,
		m3uaSgpIpspStatAspacIn            Counter32,
		m3uaSgpIpspStatAspdnIn            Counter32,
		m3uaSgpIpspStatAspiaIn            Counter32,
		m3uaSgpIpspStatNotifyOut          Counter32,
		m3uaSgpIpspStatDunaOut            Counter32,
		m3uaSgpIpspStatDavaOut            Counter32,
		m3uaSgpIpspStatDupuOut            Counter32,
		m3uaSgpIpspStatDaudIn             Counter32
	}

m3uaSgpIpspStatAssocId OBJECT-TYPE
		SYNTAX      Unsigned32
		MAX-ACCESS  not-accessible
		STATUS      current
		DESCRIPTION
			"Association Identification. It is the value that identifies
			 the association that is established between this SGP or IPSP
			 and the remote ASP or IPSP. This value is extracted from the
			 SCTP association Id value returned by SCTP when the
			 association is established to that endpoint. It is the link
			 to get the transport values from the SCTP MIB."
	::= { m3uaSgpIpspStatEntry 1 }

m3uaSgpIpspStatAspupAckOut OBJECT-TYPE
		SYNTAX      Counter32
		MAX-ACCESS  read-only
		STATUS      current
		DESCRIPTION
			"Number of ASPUP ACK messages sent through the association."
	::= { m3uaSgpIpspStatEntry 2 }

m3uaSgpIpspStatAspacAckOut OBJECT-TYPE
		SYNTAX      Counter32
		MAX-ACCESS  read-only
		STATUS      current
		DESCRIPTION
			"Number of ASPAC ACK messages sent through the association."
	::= { m3uaSgpIpspStatEntry 3 }

m3uaSgpIpspStatAspdnAckOut OBJECT-TYPE
		SYNTAX      Counter32
		MAX-ACCESS  read-only
		STATUS      current
		DESCRIPTION
			"Number of ASPDN ACK messages sent through the association."
	::= { m3uaSgpIpspStatEntry 4 }

m3uaSgpIpspStatAspiaAckOut OBJECT-TYPE
		SYNTAX      Counter32
		MAX-ACCESS  read-only
		STATUS      current
		DESCRIPTION
			"Number of ASPIA ACK messages sent through the association."
	::= { m3uaSgpIpspStatEntry 5 }

m3uaSgpIpspStatAspupIn OBJECT-TYPE
		SYNTAX      Counter32
		MAX-ACCESS  read-only
		STATUS      current
		DESCRIPTION
			"Number of ASPUP messages received through the association."
	::= { m3uaSgpIpspStatEntry 6 }

m3uaSgpIpspStatAspacIn OBJECT-TYPE
		SYNTAX      Counter32
		MAX-ACCESS  read-only
		STATUS      current
		DESCRIPTION
			"Number of ASPAC messages received through the association."
	::= { m3uaSgpIpspStatEntry 7 }

m3uaSgpIpspStatAspdnIn OBJECT-TYPE
		SYNTAX      Counter32
		MAX-ACCESS  read-only
		STATUS      current
		DESCRIPTION
			"Number of ASPDN messages received through the association."
	::= { m3uaSgpIpspStatEntry 8 }

m3uaSgpIpspStatAspiaIn OBJECT-TYPE
		SYNTAX      Counter32
		MAX-ACCESS  read-only
		STATUS      current
		DESCRIPTION
			"Number of ASPIA messages received through the association."
	::= { m3uaSgpIpspStatEntry 9 }

m3uaSgpIpspStatNotifyOut OBJECT-TYPE
		SYNTAX      Counter32
		MAX-ACCESS  read-only
		STATUS      current
		DESCRIPTION
			"Number of NOTIFY messages sent through the association."
	::= { m3uaSgpIpspStatEntry 10 }

m3uaSgpIpspStatDunaOut OBJECT-TYPE
		SYNTAX      Counter32
		MAX-ACCESS  read-only
		STATUS      current
		DESCRIPTION
			"Number of DUNA messages sent through the association."
	::= { m3uaSgpIpspStatEntry 11 }

m3uaSgpIpspStatDavaOut OBJECT-TYPE
		SYNTAX      Counter32
		MAX-ACCESS  read-only
		STATUS      current
		DESCRIPTION
			"Number of DAVA messages sent through the association."
	::= { m3uaSgpIpspStatEntry 12 }

m3uaSgpIpspStatDupuOut OBJECT-TYPE
		SYNTAX      Counter32
		MAX-ACCESS  read-only
		STATUS      current
		DESCRIPTION
			"Number of DUPU messages sent through the association."
	::= { m3uaSgpIpspStatEntry 13 }

m3uaSgpIpspStatDaudIn OBJECT-TYPE
		SYNTAX      Counter32
		MAX-ACCESS  read-only
		STATUS      current
		DESCRIPTION
			"Number of DAUD messages received through the association."
	::= { m3uaSgpIpspStatEntry 14 }

m3uaGenNaTable OBJECT-TYPE
		SYNTAX      SEQUENCE OF M3uaGenNaEntry
		MAX-ACCESS  not-accessible
		STATUS      current
		DESCRIPTION
			"A table containing Network Appearance-specific information"
	::= { m3uaGenCfg 1 }

m3uaGenNaEntry  OBJECT-TYPE
		SYNTAX      M3uaGenNaEntry
		MAX-ACCESS  not-accessible
		STATUS      current
		DESCRIPTION
			"General common variables for a Network Appearance."
		INDEX   { m3uaGenNaValue }
	::= { m3uaGenNaTable  1 }

M3uaGenNaEntry  ::= SEQUENCE {
		m3uaGenNaValue                        Unsigned32,
		m3uaGenNaNi                           Unsigned32,
		m3uaGenNaMtp3ProtType                 INTEGER,
		m3uaGenNaMtp3ProtVariant              Unsigned32,
		m3uaGenNaMtp3ProtVersion              Unsigned32
	}

m3uaGenNaValue OBJECT-TYPE
		SYNTAX      Unsigned32
		MAX-ACCESS  not-accessible
		STATUS      current
		DESCRIPTION
			"Network Appearance Value."
	::= { m3uaGenNaEntry  1 }

m3uaGenNaNi OBJECT-TYPE
		SYNTAX      Unsigned32
		MAX-ACCESS  read-only
		STATUS      current
		DESCRIPTION
			"Identifies the Network Indicator of the SG Node in the
			 SS7 Network."
	::= { m3uaGenNaEntry  2 }

m3uaGenNaMtp3ProtType OBJECT-TYPE
		SYNTAX      INTEGER {
			itu(1),
			ansi(2),
			china(3),
			ttc(4),
			other(5)
		}
		MAX-ACCESS  read-only
		STATUS      current
		DESCRIPTION
			"The MTP3 protocol type for this NA."
	::= { m3uaGenNaEntry  3 }

m3uaGenNaMtp3ProtVariant OBJECT-TYPE
		SYNTAX      Unsigned32
		MAX-ACCESS  read-only
		STATUS      current
		DESCRIPTION
			"The MTP3 protocol variant for this NA."
	::= { m3uaGenNaEntry  4 }

m3uaGenNaMtp3ProtVersion OBJECT-TYPE
		SYNTAX      Unsigned32
		MAX-ACCESS  read-only
		STATUS      current
		DESCRIPTION
			"The MTP3 protocol version for this NA."
	::= { m3uaGenNaEntry  5 }

m3uaGenStatTable OBJECT-TYPE
		SYNTAX      SEQUENCE OF M3uaGenStatEntry
		MAX-ACCESS  not-accessible
		STATUS      current
		DESCRIPTION
			"A table containing per association statistics."
	::= { m3uaGenStat 1 }

m3uaGenStatEntry OBJECT-TYPE
		SYNTAX      M3uaGenStatEntry
		MAX-ACCESS  not-accessible
		STATUS      current
		DESCRIPTION
			"It counts all the messages received and sent through a
			 specific association."
		INDEX   { m3uaGenStatAssocId }
	::= { m3uaGenStatTable 1 }

M3uaGenStatEntry ::= SEQUENCE {
		m3uaGenStatAssocId            Unsigned32,
		m3uaGenStatDataOut            Counter32,
		m3uaGenStatDataIn             Counter32,
		m3uaGenStatErrorOut           Counter32,
		m3uaGenStatErrorIn            Counter32,
		m3uaGenStatSconOut            Counter32,
		m3uaGenStatSconIn             Counter32
	}

m3uaGenStatAssocId OBJECT-TYPE
		SYNTAX      Unsigned32
		MAX-ACCESS  not-accessible
		STATUS      current
		DESCRIPTION
			"Association Identification. It is the value that identifies
			 the association that is established between an ASP and an SGP
			 or between 2 IPSPs. This value is extracted from the SCTP
			 association Id value returned by SCTP when the association is
			 established to that endpoint. It is the link to get the
			 transport values from the SCTP MIB."
	::= { m3uaGenStatEntry 1 }

m3uaGenStatDataOut OBJECT-TYPE
		SYNTAX      Counter32
		MAX-ACCESS  read-only
		STATUS      current
		DESCRIPTION
			"Number of DATA messages sent through the association."
	::= { m3uaGenStatEntry 2 }

m3uaGenStatDataIn OBJECT-TYPE
		SYNTAX      Counter32
		MAX-ACCESS  read-only
		STATUS      current
		DESCRIPTION
			"Number of DATA messages received through the association."
	::= { m3uaGenStatEntry 3 }

m3uaGenStatErrorOut OBJECT-TYPE
		SYNTAX      Counter32
		MAX-ACCESS  read-only
		STATUS      current
		DESCRIPTION
			"Number of ERROR messages sent through the association."
	::= { m3uaGenStatEntry 4 }

m3uaGenStatErrorIn OBJECT-TYPE
		SYNTAX      Counter32
		MAX-ACCESS  read-only
		STATUS      current
		DESCRIPTION
			"Number of ERROR messages received through the association."
	::= { m3uaGenStatEntry 5 }

m3uaGenStatSconOut OBJECT-TYPE
		SYNTAX      Counter32
		MAX-ACCESS  read-only
		STATUS      current
		DESCRIPTION
			"Number of SCON messages sent through the association."
	::= { m3uaGenStatEntry 6 }

m3uaGenStatSconIn OBJECT-TYPE
		SYNTAX      Counter32
		MAX-ACCESS  read-only
		STATUS      current
		DESCRIPTION
			"Number of SCON messages received through the association."
	::= { m3uaGenStatEntry 7 }

m3uaCompliances OBJECT IDENTIFIER ::= { m3uaConformance 1 }
m3uaGroups      OBJECT IDENTIFIER ::= { m3uaConformance 2 }

m3uaAttributesGroup OBJECT-GROUP
		OBJECTS   {
			m3uaVersion,
			m3uaProcType,
			m3uaLocalPort,
			m3uaTrInitValue,
			m3uaTBeatInitValue,
			m3uaTAckInitValue,
			m3uaTPAudInitValue,
			m3uaHeartBeat,
			m3uaRoutingFailures
		}
		STATUS    current
		DESCRIPTION
			"The m3ua group of objects providing for management of M3UA
			 entities. Common parameters for the protocol."
	::= { m3uaGroups 1 }

m3uaAspCfgGroup OBJECT-GROUP
		OBJECTS   {
			m3uaAspDestState,
			m3uaAspSgpState,
			m3uaAspAssocId,
			m3uaAspAssocMinOutStreams,
			m3uaAspAssocMaxInStreams,
			m3uaAspRcValue
		}
		STATUS    current
		DESCRIPTION
			"The m3ua group of objects to describe configuration values
			 at the Application Server Process (ASP)."
	::= { m3uaGroups 2 }

m3uaAspStatsGroup OBJECT-GROUP
		OBJECTS   {
			m3uaAspStatAspupOut,
			m3uaAspStatAspacOut,
			m3uaAspStatAspdnOut,
			m3uaAspStatAspiaOut,
			m3uaAspStatAspupAckIn,
			m3uaAspStatAspacAckIn,
			m3uaAspStatAspdnAckIn,
			m3uaAspStatAspiaAckIn,
			m3uaAspStatNotifyIn,
			m3uaAspStatDaudOut,
			m3uaAspStatDunaIn,
			m3uaAspStatDavaIn,
			m3uaAspStatDupuIn
		}
		STATUS    current
		DESCRIPTION
			"The m3ua group of objects to count how the number of
			 messages received/send by an ASP. Most of these messages
			 applies to the M3UA client process and would also apply to an
			 IPSP acting as a client."
	::= { m3uaGroups 3 }

m3uaSgpIpspCfgGroup OBJECT-GROUP
		OBJECTS   {
			m3uaSgpIpspRtgAsId,
			m3uaSgpIpspRtgRc,
			m3uaSgpIpspAsState,
			m3uaSgpIpspAsTmt,
			m3uaSgpIpspAspState,
			m3uaSgpIpspAspRole,
			m3uaSgpIpspAssocId,
			m3uaSgpIpspAssocMinOutStreams,
			m3uaSgpIpspAssocMaxInStreams
		}
		STATUS    current
		DESCRIPTION
			"The m3ua group of objects to describe configuration values
			 at either the Signaling Gateway Process (SGP) or the IP
			 Server Process (IPSP)."
	::= { m3uaGroups 4 }

m3uaSgpIpspStatsGroup OBJECT-GROUP
		OBJECTS   {
			m3uaSgpIpspStatAspupAckOut,
			m3uaSgpIpspStatAspacAckOut,
			m3uaSgpIpspStatAspdnAckOut,
			m3uaSgpIpspStatAspiaAckOut,
			m3uaSgpIpspStatAspupIn,
			m3uaSgpIpspStatAspacIn,
			m3uaSgpIpspStatAspdnIn,
			m3uaSgpIpspStatAspiaIn,
			m3uaSgpIpspStatNotifyOut,
			m3uaSgpIpspStatDunaOut,
			m3uaSgpIpspStatDavaOut,
			m3uaSgpIpspStatDupuOut,
			m3uaSgpIpspStatDaudIn
		}
		STATUS    current
		DESCRIPTION
			"The m3ua group of objects to count how the number of
			 messages received/send by a Signaling Process or IPSP."
	::= { m3uaGroups 5 }

m3uaGenCfgGroup OBJECT-GROUP
		OBJECTS   {
			m3uaGenNaNi,
			m3uaGenNaMtp3ProtType,
			m3uaGenNaMtp3ProtVariant,
			m3uaGenNaMtp3ProtVersion
		}
		STATUS    current
		DESCRIPTION
			"The m3ua group of objects to describe the Network Appearance
			 (NA) value."
	::= { m3uaGroups 6 }

m3uaGenStatsGroup OBJECT-GROUP
		OBJECTS   {
			m3uaGenStatDataOut,
			m3uaGenStatDataIn,
			m3uaGenStatErrorOut,
			m3uaGenStatErrorIn,
			m3uaGenStatSconOut,
			m3uaGenStatSconIn
		}
		STATUS    current
		DESCRIPTION
			"The m3ua group of objects to count how the number of
			 messages received/send by a Signaling Process. This objects
			 are implemented in all kind of signaling processes: ASPs,
			 SGPs and IPSPs."
	::= { m3uaGroups 7 }

m3uaAspCompliance MODULE-COMPLIANCE
		STATUS  current
		DESCRIPTION
			"The compliance statement for Application Server Processes (ASP)
			 that implement this MIB in order to be managed using SNMP
			 protocol."
		MODULE  -- this module
		MANDATORY-GROUPS { m3uaAttributesGroup,
			m3uaAspCfgGroup,
			m3uaGenCfgGroup,
			m3uaAspStatsGroup,
			m3uaGenStatsGroup
		}
	::= { m3uaCompliances 1 }

m3uaSgpCompliance MODULE-COMPLIANCE
		STATUS  current
		DESCRIPTION
			"The compliance statement for Signaling Gateway Processes (SGP)
			 that implement this MIB in order to be managed using SNMP
			 protocol."
		MODULE  -- this module
		MANDATORY-GROUPS { m3uaAttributesGroup,
			m3uaSgpIpspCfgGroup,
			m3uaGenCfgGroup,
			m3uaSgpIpspStatsGroup,
			m3uaGenStatsGroup
		}
	::= { m3uaCompliances 2 }

m3uaIpspCompliance MODULE-COMPLIANCE
		STATUS  current
		DESCRIPTION
			"The compliance statement IP Server Processes (IPSP) that
			 implement this MIB in order to be managed using SNMP protocol."
		MODULE  -- this module
		MANDATORY-GROUPS { m3uaAttributesGroup,
			m3uaSgpIpspCfgGroup,
			m3uaGenCfgGroup,
			m3uaAspStatsGroup,
			m3uaSgpIpspStatsGroup,
			m3uaGenStatsGroup
		}
	::= { m3uaCompliances 3 }

END
